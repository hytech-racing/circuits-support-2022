#require 9.06020

#usage "<b>Set all SIGNAL attributes to signal name</b>\n"
       "<p>This script loops through all signals in a board to find all TP* parts "
       "and then edits their SIGNAL attribute to be the signal name and adjusts the"
       "text to be the right formatting."
       "<author>Author: Arvind Srinivasan</author>"

string ftoa (real f) {
  string str = "";
  sprintf(str, "%f", f);
  return str;
}

if (board) {
    string cmd;
    board(B) {  // loop through board
        B.signals(S) { // loop through signals
            S.contactrefs(C) { // loop through contacts
                if (strsub(C.element.name,0,2) == "TP") { // if the contact has a element whose name starts with "TP"
                    cmd += "ATTRIBUTE " + C.element.name + " SIGNAL '" + S.name + "'; "; // set SIGNAL attribute
                    C.element.texts(T) { // loop through texts
                        if(S.name == T.value) { // if text is signal attribute text
                            cmd += "CHANGE DISPLAY VALUE (" + ftoa(u2mil(T.x)) + " " + ftoa(u2mil(T.y)) + "); ";
                            cmd += "CHANGE FONT VECTOR ("+ ftoa(u2mil(T.x)) + " " + ftoa(u2mil(T.y)) + "); ";
                            cmd += "CHANGE SIZE 32 ("+ ftoa(u2mil(T.x)) + " " + ftoa(u2mil(T.y)) + "); ";
                            cmd += "CHANGE RATIO 8 ("+ ftoa(u2mil(T.x)) + " " + ftoa(u2mil(T.y)) + "); \n";
                        }
                    }
                }
            }
        }
    }
   exit (cmd); // exit and run the command
}
else { // we're not in a board
   dlgMessageBox("\n    Start this ULP in a Board    \n");
   exit (0); // exit
}
